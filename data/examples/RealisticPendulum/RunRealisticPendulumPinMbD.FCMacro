# SPDX-License-Identifier: LGPL-2.1-or-later

"""Run the pin MbD example after FreeCAD's delayed startup finishes."""

from pathlib import Path

from PySide6 import QtCore


def _run_example(
    script_path=str(Path(__file__).with_name("CreateRealisticPendulumPinMbD.py")),
):
    import runpy
    import traceback

    import FreeCAD as App

    App.Console.PrintMessage(f"Running {script_path}\n")
    try:
        runpy.run_path(script_path, run_name="__main__")
    except Exception:
        App.Console.PrintError(traceback.format_exc())


QtCore.QTimer.singleShot(0, _run_example)
